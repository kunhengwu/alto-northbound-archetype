module alto-nbr-${artifactId} {
    yang-version 1;
    namespace "urn:opendaylight:alto:core:northbound:route:${artifactIdInYang}";
    prefix "alto-nbr-${artifactIdInYang}";

    import config { prefix config; revision-date 2013-04-05; }
    import ietf-inet-types { prefix ietf-inet; revision-date 2013-07-15; }

    organization "Yale University";

    contact "alto-dev@lists.opendaylight.org";

    revision "2015-01-05" {
        description "Initial revision of ${artifactIdInYang} model";
    }

    container "records" {
        list "record" {
            key "path";

            leaf "path" {
                type ietf-inet:uri;
            }

            leaf "resource-iid" {
                type instance-identifier;
            }
        }
    }
}
